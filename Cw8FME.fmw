FME workspace Cw8FME.fmw

Parameters:
- DestDataset_GEOJSON = $(FME_MF_DIR)Dane - Ćwiczenia 8\cw8-zad6.json   # Destination GeoJSON File
- DestDataset_GEODATABASE_FILE_3 = $(FME_MF_DIR)Dane - Ćwiczenia 8\bezkosztów.gdb   # File Geodatabase
- DestDataset_GEODATABASE_FILE = $(FME_MF_DIR)Dane - Ćwiczenia 8\zkosztami.gdb   # File Geodatabase
- SourceDataset_SHAPEFILE_7 = $(FME_MF_DIR)Dane - Ćwiczenia 8\Karlsruhe_Germany_Shapefile\T2019_KAR_STREET_NODE.shp   # Source Esri Shapefile(s)
- SourceDataset_SHAPEFILE_6 = $(FME_MF_DIR)Dane - Ćwiczenia 8\Karlsruhe_Germany_Shapefile\T2019_KAR_POI_TABLE.shp   # Source Esri Shapefile(s)
- SourceDataset_SHAPEFILE = $(FME_MF_DIR)Dane - Ćwiczenia 8\Karlsruhe_Germany_Shapefile\T2019_KAR_STREETS.shp   # Source Esri Shapefile(s)
- SourceDataset_CSV2 = $(FME_MF_DIR)Dane - Ćwiczenia 8\routePoints.csv   # Source CSV (Comma Separated Value) File(s)

Readers:
- SHAPEFILE_3: SHAPEFILE from $(SourceDataset_SHAPEFILE_7)
- SHAPEFILE_4: SHAPEFILE from $(SourceDataset_SHAPEFILE_6)
- SHAPEFILE_1: SHAPEFILE from $(SourceDataset_SHAPEFILE)
- CSV2_1: CSV2 from $(SourceDataset_CSV2)

Writers:
- GEOJSON_1: GEOJSON to $(DestDataset_GEOJSON)
- GEODATABASE_FILE_1: GEODATABASE_FILE to $(DestDataset_GEODATABASE_FILE)
- GEODATABASE_FILE_2: GEODATABASE_FILE to $(DestDataset_GEODATABASE_FILE_3)

T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> T2019_KAR_STREETS
    -> Reprojector_3
Reprojector_3
    DEST = DHDN.Berlin/Cassini
    INTERPOLATION_TYPE_NAME = Nearest Neighbor
    RASTER_CELL_SIZE = Preserve Cells
    RASTER_TOLERANCE = 0.0
    SOURCE = EPSG:4326
    REPROJECTED -> ShortestPathFinder [NETWORK]
    REPROJECTED -> Tester
Tester
    BOOL_OP = OR
    TEST_CLAUSE:
      TEST @Value(DIR_TRAVEL) = B
      TEST @Value(DIR_TRAVEL) = T
    TEST_MODE = TEST
    PASSED -> AttributeManager
    FAILED -> AttributeManager_2
AttributeManager
    ATTR_TABLE:
      SET_TO FORWARD_COST = 1
      SET_TO REVERSE_COST = 1
    -> ShortestPathFinder_2 [NETWORK]
AttributeManager_2
    ATTR_TABLE:
      SET_TO FORWARD_COST = 1
      SET_TO REVERSE_COST = 9999
    -> ShortestPathFinder_2 [NETWORK]
T2019_KAR_STREETS: Inspector
CSV (reader CSV2_1)
    attributes: x x_coordinate, y y_coordinate
    -> VertexCreator
VertexCreator
    CLOSE_LINES = Yes
    IGNORE_DUPLICATES = No
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    LINE -> Reprojector_2
Reprojector_2
    DEST = DHDN.Berlin/Cassini
    INTERPOLATION_TYPE_NAME = Nearest Neighbor
    RASTER_CELL_SIZE = Preserve Cells
    RASTER_TOLERANCE = 0.0
    SOURCE = EPSG:4326
    REPROJECTED -> ShortestPathFinder [FROM-TO]
    REPROJECTED -> ShortestPathFinder_2 [FROM-TO]
ShortestPathFinder_2
    ALLOW_UTURNS = Yes
    REORDER_CHOICE = None
    SNAP_POINTS = Yes
    SNAP_TOLERANCE = 200
    WEIGHT_ATTR_1 = FORWARD_COST
    WEIGHT_ATTR_2 = REVERSE_COST
    WEIGHT_ATTR_CHOICE = BY_TWO_ATTRIBUTES
    PATH -> Bufferer_2
    PATH -> PointOnLineOverlayer [LINE]
    PATH -> LengthCalculator
LengthCalculator
    DIM = 2
    LEN_ATTR = _length
    MULT = 1
    -> FeatureMerger [SUPPLIER]
Bufferer_2
    ANGLE = 22.5
    CAP_STYLE = Arc
    CORNER_STYLE = Arc
    MODE = AREA
    OFFSET = 5
    OFFSET_UNITS = METERS
    PRECISION = APPROX
    BUFFERED -> SpatialFilter_2 [Filter]
ShortestPathFinder
    ALLOW_UTURNS = Yes
    REORDER_MODE = NONE
    SNAP_POINTS = Yes
    SNAP_TOLERANCE = 200
    WEIGHT_ATTR_CHOICE = BY_LENGTH
    PATH -> Bufferer
    PATH -> PointOnLineOverlayer_2 [LINE]
    PATH -> LengthCalculator_2
Bufferer
    ANGLE = 22.5
    CAP_STYLE = Arc
    CORNER_STYLE = Arc
    MODE = AREA
    OFFSET = 5
    OFFSET_UNITS = METERS
    PRECISION = APPROX
    BUFFERED -> SpatialFilter [Filter]
LengthCalculator_2
    DIM = 2
    LEN_ATTR = _length
    MULT = 1
    -> FeatureMerger_2 [SUPPLIER]
T2019_KAR_POI_TABLE (reader SHAPEFILE_4)
    attributes: POI_ID long, LINK_ID long, TYPE varchar(250), POI_NAME varchar(250), ST_NAME varchar(250), LAT number(31,15), LON number(31,15)
    -> T2019_KAR_POI_TABLE
    -> Reprojector
T2019_KAR_POI_TABLE: Inspector
Reprojector
    DEST = DHDN.Berlin/Cassini
    INTERPOLATION_TYPE_NAME = Nearest Neighbor
    RASTER_CELL_SIZE = Preserve Cells
    RASTER_TOLERANCE = 0.0
    SOURCE = EPSG:4326
    REPROJECTED -> SpatialFilter [Candidate]
    REPROJECTED -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> cw8-zad6 (writer GEOJSON_1)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> cw8-zad6 (writer GEOJSON_1)
cw8-zad6 (writer GEOJSON_1)
    attributes: POI_ID int, LINK_ID int, TYPE string, POI_NAME string, ST_NAME string, LAT float, LON float
T2019_KAR_STREET_NODE (reader SHAPEFILE_3)
    attributes: NODE_ID long, LINK_ID long, POINT_NUM long, Z_LEVEL long, INTERSECT varchar(1), LAT number(31,15), LON number(31,15)
    -> T2019_KAR_STREET_NODE
    -> Reprojector_4
T2019_KAR_STREET_NODE: Inspector
Reprojector_4
    DEST = DHDN.Berlin/Cassini
    INTERPOLATION_TYPE_NAME = Nearest Neighbor
    RASTER_CELL_SIZE = Preserve Cells
    RASTER_TOLERANCE = 0.0
    SOURCE = EPSG:4326
    REPROJECTED -> PointOnLineOverlayer [POINT]
    REPROJECTED -> PointOnLineOverlayer_2 [POINT]
PointOnLineOverlayer
    DEAGGREGATE_INPUT = Yes
    MEASURE_TYPE = Continuous
    MERGE_MEASURES = Yes
    OV_ATTR = _overlaps
    TOLERANCE = 0
    POINT -> Tester_2
Tester_2
    BOOL_OP = OR
    TEST_CLAUSE = TEST @Value(_overlaps) = 1
    TEST_MODE = TEST
    PASSED -> StatisticsCalculator
StatisticsCalculator
    CALCULATION_MODE = NUMERIC
    FEAT_STATS = LAT,NUMERIC_MODE,MIN,MAX,,SUM,MEAN,MEDIAN,,,,,,,;LON,NUMERIC_MODE,MIN,MAX,,SUM,MEAN,MEDIAN,,,,,,,
    COMPLETE -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> zkosztami (writer GEODATABASE_FILE_1)
zkosztami (writer GEODATABASE_FILE_1)
    attributes: NODE_ID integer, LINK_ID integer, POINT_NUM integer, Z_LEVEL integer, INTERSECT char(1), LAT double(31,15), LON double(31,15)
PointOnLineOverlayer_2
    DEAGGREGATE_INPUT = Yes
    MEASURE_TYPE = Continuous
    MERGE_MEASURES = Yes
    OV_ATTR = _overlaps
    TOLERANCE = 0
    POINT -> Tester_3
Tester_3
    BOOL_OP = OR
    TEST_CLAUSE = TEST @Value(_overlaps) = 1
    TEST_MODE = TEST
    PASSED -> StatisticsCalculator_2
StatisticsCalculator_2
    CALCULATION_MODE = NUMERIC
    FEAT_STATS = LAT,NUMERIC_MODE,MIN,MAX,,SUM,MEAN,MEDIAN,,,,,,,;LON,NUMERIC_MODE,MIN,MAX,,SUM,MEAN,MEDIAN,,,,,,,
    COMPLETE -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> bezkosztow (writer GEODATABASE_FILE_2)
bezkosztow (writer GEODATABASE_FILE_2)
    attributes: NODE_ID integer, LINK_ID integer, POINT_NUM integer, Z_LEVEL integer, INTERSECT char(1), LAT double(31,15), LON double(31,15)
